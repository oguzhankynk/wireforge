# SRS sample

## HLR-NAV-001
The navigation solution shall be sent to nodeA with its position inside the valid geographic range.

## HLR-NAV-002
The number of tracks in a navigation solution shall not exceed the platform limit.

## HLR-NBS-001
The status burst of nodeB shall be accepted without a header and with a variable diagnostic tail.

## HLR-CMD-001
Commands to nodeC shall carry the vendor checksum.

## HLR-LNK-001
Frames to nodeA shall be protected by a CRC-16 and recovered after corrupted data.
